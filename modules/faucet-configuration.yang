module faucet-configuration {

  yang-version "1";

  // namespace
  namespace "http://www.github.com/faucet";

  // Assign this module a prefix to be used by other modules, when imported.
  prefix "faucet-conf";

  import ietf-inet-types {
    prefix "inet";
  }

  import ietf-yang-types {
    prefix yang;
  }

  import ietf-ethertypes {
    prefix eth;
  }


  // meta
  organization "faucet";

  contact
    "None";

  description
    "This module defines the top level faucet Configurations.";

  revision "2017-12-04" {
    description
      "Initial version";
    reference "0.1.0";
  }

 typedef hex{
     type string {
       pattern '0x[0-9a-fA-F]+';
     }
}

//typedef ipv4-add{
//    type string{
//      pattern '(([0-9]|[1-9][0-9]|1[0-9][0-9]|2[0-4][0-9]|25[0-5])\.){3}([0-9]|[1-9][0-9]|1[0-9][0-9]|2[0-4][0-9]|25[0-5])/(([1-2][0-9])|(3[0-2])|([0-9]))|((([0-9]|[1-9][0-9]|1[0-9][0-9]|2[0-4][0-9]|25[0-5])\.){3}([0-9]|[1-9][0-9]|1[0-9][0-9]|2[0-4][0-9]|25[0-5])(%[\p{N}\p{L}]+)?)'
//  }
//}
 grouping faucet-top {
    description
      "Top-level grouping for faucet configuration.";

leaf ver_sion {
    type uint8;
    default "2";
    description "The faucet yang version.";
     }       

list dps{
    description "This is a dps list";
    key "dp_name";
    ordered-by user;
    unique "dp_id";

    leaf dp_name{
        type string {
          length "1..64";
        }
       }
    leaf desciption{
        type string {
          length "1..255";
        }
       }
   leaf dp_id {
       type hex;
 // type uint64;
   }       

    leaf hardware{
        type string {
          length "1..64";
        }
      }

   list interfaces{
     description "This is a dps list";
     ordered-by user;

     key "number";
     unique "name";

     leaf name{
        type string {
          length "1..64";
        }
     }    
    leaf number{
    type uint8;
    }

    leaf description{
    type string {
         length "3..255";
        }
    }

    leaf acl_in {
     type leafref {
       path "/faucet-conf:acls/acls:acl-name";
     }
      description
        "The name of the ACL for this entry.";
    }

    leaf mirror {
     type leafref {
       path "../../interfaces/number";
     }    
    description "mirror all in/out flows to another port..";
    }
   
   }// interfaces

 }// dps


 list vlans{
      description "This is a list of vlans.";
       key "vid";
      ordered-by user;

      leaf vid {
        type uint16;
        }

    leaf max_hosts {
        type uint16;
        default "255";
        description "The MTU of the interface.";
        }          

     leaf name{
        type string {
          length "1..64";
        }
       }
   }

list acls{
     description "list of acls ";
      key "acl-name";
      ordered-by user;
      leaf acl-name {
        type string {
          length "1..64";
        }
      }
 list acle {
      description "This is a list of users in the system.";
      key "acle-name";
      ordered-by user;

      leaf acle-name {
        type string {
          length "1..64";
        }
        description
          "The name of access-list. A device MAY restrict the length
           and value of this name, possibly space and special
           characters are not allowed.";
      }

      container actions {
        description "actions for this acl entry ";

        leaf allow {
          type uint8;
         }          

         leaf mirror {
           type leafref {
            path "/faucet-conf:dps/interfaces/number";
           }         
         }
         container output{
          leaf port{
           type leafref {
            path "/faucet-conf:dps/interfaces/number";
           }          
           description "destination port to output matched packets to.";
          }  
         }

      } // end actions container   

   container match{

  //mac
          leaf dl_type_name {
          type eth:ethertype;
         }   

        leaf dl_type {
          type hex;
         }   
        leaf dl_src {
          type yang:mac-address;
         }   
        leaf dl_dst {
          type yang:mac-address;
         }   
//ip 
      leaf nw_proto {
        type uint8;
      }
//ipv4
      leaf ipv4_src {
        type inet:ipv4-address;
      }
      leaf ipv4_dst {
        type inet:ipv4-address;
      }
//ipv6
      leaf ipv6_src {
        type inet:ipv6-address;
      }
      leaf ipv6_dst {
        type inet:ipv6-address;
      }
// tcp/udp
      leaf tcp_src {
        type inet:port-number;
      }
      leaf tcp_dst {
        type inet:port-number;
      }
      leaf udp_src {
        type inet:port-number;
      }
      leaf udp_dst {
        type inet:port-number;
        }   

 }//match cont
 }//acle
} //acls

  }//end group

  uses faucet-top;
}
