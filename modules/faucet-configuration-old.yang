module faucet-configuration-old {

  yang-version "1";

  // namespace
  namespace "http://www.github.com/faucet";

  // Assign this module a prefix to be used by other modules, when imported.
  prefix "faucet-conf";

  import ietf-inet-types {
    prefix "inet";
  }

  import ietf-yang-types {
    prefix yang;
  }

  import ietf-ethertypes {
    prefix eth;
  }

 import ietf-packet-fields {
    prefix pf;
  }

  // meta
  organization "faucet";

  contact
    "None";

  description
    "This module defines the top level faucet Configurations.";

  revision "2017-12-04" {
    description
      "Initial version";
    reference "0.1.0";
  }


 grouping faucet-top {
    description
      "Top-level grouping for faucet configuration.";

leaf version {
    type uint8;
    default "2";
    description "The faucet yang version.";
     }       

list dps{
    description "This is a dps list";
    key "dp-name";
    ordered-by user;
    unique "dp-id";

    leaf dp-name{
        type string {
          length "1..64";
        }
       }

    leaf dp-id {
        type yang:mac-address;
        }

    leaf hardware{
        type string {
          length "1..64";
        }
      }

   list interfaces{
     description "This is a dps list";
     ordered-by user;

     key "number";
     unique "name";

     leaf name{
        type string {
          length "1..64";
        }
     }    
    leaf number{
    type uint8;
    }

    leaf description{
    type string {
         length "3..255";
        }
    }

    leaf acl-in {
     type leafref {
       path "/faucet-conf:acls/acls:acl-name";
     }
      description
        "The name of the ACL for this entry.";
    }

    leaf mirror {
     type leafref {
       path "../../interfaces/number";
     }    
    description "mirror all in/out flows to another port..";
    }
   
   }// interfaces

 }// dps


 list vlans{
      description "This is a list of vlans.";
       key "vid";
      ordered-by user;

      leaf vid {
        type uint16;
        }

    leaf max_hosts {
        type uint16;
        default "255";
        description "The MTU of the interface.";
        }          

     leaf name{
        type string {
          length "1..64";
        }
       }
   }

list acls{
     description "list of acls ";
      key "acl-name";
      ordered-by user;
      leaf acl-name {
        type string {
          length "1..64";
        }
      }
 list acle {
      description "This is a list of users in the system.";
      key "acle-name";
      ordered-by user;

      leaf acle-name {
        type string {
          length "1..64";
        }
        description
          "The name of access-list. A device MAY restrict the length
           and value of this name, possibly space and special
           characters are not allowed.";
      }

      container actions {
        description "actions for this acl entry ";

        leaf allow {
          type uint8;
         }          

         leaf mirror {
           type leafref {
            path "/faucet-conf:dps/interfaces/number";
           }         
         }
         
         container output{
          leaf port{
           type leafref {
            path "/faucet-conf:dps/interfaces/number";
           }          
           description "destination port to output matched packets to.";
          }  
         }

      } // end actions container   

   container match{
    container ethacl{
       uses pf:acl-eth-header-fields;
     description 
        "eth acl";
    }
   container ipv4acl {
    uses pf:acl-ipv4-header-fields;
    leaf source-ipv4{
         type inet:ipv4-address;
         }
    leaf destination-ipv4{
         type inet:ipv4-address;
         }
      description
           "Rule set that supports IPv4 headers.";
     }
  container tcpacl{
    uses pf:acl-tcp-header-fields;
        leaf port {
          type inet:port-number;
          mandatory true;
          description
            "Port number along with operator on which to
             match.";
        }
    }
 }//match cont
 }//acle
} //acls

  }//end group
  uses faucet-top;
}
